-- Module Uds2 (F.515:04/2003)
-- See also ITU-T F.515 (04/2003)
-- See also the index of all ASN.1 assignments needed in this document

Uds2 DEFINITIONS AUTOMATIC TAGS ::=
BEGIN

Entry ::= SEQUENCE {
  entryIdentifier  OCTET STRING OPTIONAL,
  hierarchyLevel   INTEGER(0..MAX) OPTIONAL,
  hierarchyBelow   BOOLEAN DEFAULT FALSE,
  options          SEQUENCE {attribute  INTEGER, -- Attribute
                           family     BOOLEAN, -- Family 
                          }
}

END
-- Generated by Asnp, the ASN.1 pretty-printer of France Telecom R&D
